--
-- RFC7633 heavily modified ASN.1 Module.
-- For use with syntactic linter.
-- Fotis Loukos
--

TLS-Feature-Module-2015 {
    iso(1) identified-organization(3) dod(6) internet(1)
    security(5) mechanisms(5) pkix(7) id-mod(0)
    id-mod-tls-feature-2015(86)}

DEFINITIONS IMPLICIT TAGS ::=
BEGIN

    IMPORTS -- From RFC 5280

    id-pe
    FROM PKIX1Explicit88 {
        iso(1) identified-organization(3) dod(6) internet(1)
        security(5) mechanisms(5) pkix(7) id-mod(0)
        id-mod-pkix1-explicit-02(51)}
    ;

    id-pe-tlsfeature OBJECT IDENTIFIER ::= { id-pe 24 }

    Features ::= SEQUENCE OF INTEGER

END
