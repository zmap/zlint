-- 
-- ASN.1 module for Signed HTTP Exchanges.
-- For use with syntactic linter. Official module uses the 2008 syntax which is incompatible with asn1c.
-- Fotis Loukos
-- 

SXGModule DEFINITIONS ::=

BEGIN

-- EXPORTS ALL

id-ce-canSignHttpExchanges OBJECT IDENTIFIER ::= { 1 3 6 1 4 1 11129 2 1 22 }

CanSignHttpExchanges ::= NULL

END
